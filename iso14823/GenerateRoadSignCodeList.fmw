FME workspace GenerateRoadSignCodeList.fmw

Parameters:
- SourceDataset_XLSXR = C:\DATA\GitHub\vegvesen\TN-ITS\UML (EA)\TS14823-Pictgram-catalogue-21_July.xlsx   # Source Microsoft Excel File(s)
- DestDataset_TEXTLINE = C:\DATA\GitHub\jetgeo\GIS2OWL\iso14823   # Destination Text File
- SourceDataset_XLSXR_3 = C:\DATA\GitHub\vegvesen\TN-ITS\UML (EA)\TS14823-Pictgram-catalogue-21_July.xlsx   # Source Microsoft Excel File(s)

Readers:
- XLSXR_1: XLSXR from $(SourceDataset_XLSXR)
- XLSXR_2: XLSXR from $(SourceDataset_XLSXR_3)

Writers:
- TEXTLINE_1: TEXTLINE to $(DestDataset_TEXTLINE)

Ambient Road Condition (31) (reader XLSXR_2)
    attributes: Traffic sign for  char(42), GDD code char(17), GDD code00 char(19), Related attributes char(19), U.N./Vienna char(12), Germany char(8), France char(7), UK char(3), Italy char(6), Spain char(6), Netherlands char(12), Belgium char(8), Switzerland char(12), Austria char(8), Ireland char(8), Poland char(7), Sweden char(7), Finland char(8), Norway char(7), Greece char(7), Czech Rep char(10), Slovakia char(9), Russia & Belarus char(17), U.S. char(5), Request by NL char(14), Request by AT char(14), Request by DE char(14), South Korea char(12), Japan char(6), AD string,
      AE string, AF string, AG string, AH string, AI string, AJ string, AK string, AL string, AM string, AN string
    -> AttributeManager_4
Guide(13) (reader XLSXR_2)
    attributes: Traffic sign for  char(70), GDD code char(17), GDD code00 char(19), Related attributes char(118), U.N./Vienna char(12), Germany char(8), France char(7), UK char(3), Italy char(6), Spain char(6), Netherlands char(12), Belgium char(8), Switzerland char(12), Austria char(8), Ireland char(8), Poland char(7), Sweden char(7), Finland char(8), Norway char(7), Greece char(7), Czech Rep char(10), Slovakia char(9), Russia & Belarus char(17), U.S. char(5), South Korea char(12), Japan char(6), AA string, AB string, AC string
    -> AttributeManager_4
Public Facilities (21) (reader XLSXR_2)
    attributes: Traffic sign for  char(38), GDD code char(17), GDD code00 char(19), Related attributes char(21), U.N./Vienna char(12), Germany char(8), France char(7), UK char(3), Italy char(6), Spain char(6), Netherlands char(12), Belgium char(8), Switzerland char(12), Austria char(8), Ireland char(8), Poland char(7), Sweden char(7), Finland char(8), Norway char(7), Greece char(7), Czech Rep char(10), Slovakia char(9), Russia & Belarus char(17), U.S. char(5), South Korea char(12), Japan char(6)
    -> AttributeManager_4
Regulatory(12) (reader XLSXR_2)
    attributes: Traffic sign for  char(135), GDD code char(17), GDD code00 char(19), GDD code01 char(19), Related attributes char(167), U.N./Vienna char(12), Germany char(8), France char(7), UK char(3), Italy char(6), Spain char(6), Netherlands char(12), Belgium char(8), Switzerland char(12), Austria char(8), Ireland char(8), Poland char(7), Sweden char(7), Finland char(8), Norway char(7), Greece char(7), Czech Rep char(10), Slovakia char(9), Russia & Belarus char(17), U.S. char(5), South Korea char(12), Japan char(6)
    -> AttributeManager_4
Warning (11) (reader XLSXR_2)
    attributes: Traffic sign for  char(101), GDD code char(17), GDD code00 char(19), GDD code01 char(19), Related attributes char(31), U.N./Vienna char(18), Germany char(8), France char(7), UK char(3), Italy char(6), Spain char(6), Netherlands char(12), Belgium char(8), Switzerland char(12), Austria char(8), Ireland char(8), Poland char(7), Sweden char(7), Finland char(8), Norway char(7), Greece char(7), Czech Rep char(10), Slovakia char(9), Russia & Belarus char(17), U.S. char(5), South Korea char(12), Japan char(6), AB string
    -> AttributeManager_4
Regulatory(12) (reader XLSXR_1) [off]
    attributes: Traffic sign for  char(135), service Category number(3,0), Pictogram Category number(4,0), Pictogram Category00 number(4,0), Related attributes char(167), U.N./Vienna char(9), Germany string, France string, UK string, Italy string, Spain string, Netherlands string, Belgium string, Switzerland string, Austria string, Ireland string, Poland string, Sweden string, Finland string, Norway string, Greece string, Czech Rep string, Slovakia string, Russia & Belarus string, U.S. string, South Korea string, Japan string
    -> AttributeManager_4
Guide(13) (reader XLSXR_1) [off]
    attributes: Traffic sign for  char(70), service Category number(3,0), Pictogram Category number(4,0), Related attributes char(118), U.N./Vienna char(8), Germany string, France string, UK string, Italy string, Spain string, Netherlands string, Belgium string, Switzerland string, Austria string, Ireland string, Poland string, Sweden string, Finland string, Norway string, Greece string, Czech Rep string, Slovakia string, Russia & Belarus string, U.S. string, South Korea string, Japan string, AA string, AB string, AC string
    -> AttributeManager_4
Ambient Road Condition (31) (reader XLSXR_1) [off]
    attributes: Traffic sign for  char(42), service Category number(3,0), Pictogram Category number(4,0), Related attributes string, U.N./Vienna string, Germany string, France string, UK string, Italy string, Spain string, Netherlands string, Belgium string, Switzerland string, Austria string, Ireland string, Poland string, Sweden string, Finland string, Norway string, Greece string, Czech Rep string, Slovakia string, Russia & Belarus string, U.S. string, Request by NL char(2), Request by AT string, Request by DE string, South Korea string, Japan string, AD string,
      AE string, AF string, AG string, AH string, AI string, AJ string, AK string, AL string, AM string, AN string
    -> AttributeManager_4
Public Facilities (21) (reader XLSXR_1) [off]
    attributes: Traffic sign for  char(38), service Category number(3,0), Pictogram Category number(4,0), Related attributes char(21), U.N./Vienna string, Germany string, France string, UK string, Italy string, Spain string, Netherlands string, Belgium string, Switzerland string, Austria string, Ireland string, Poland string, Sweden string, Finland string, Norway string, Greece string, Czech Rep string, Slovakia string, Russia & Belarus string, U.S. string, South Korea string, Japan string
    -> AttributeManager_4
Warning (11) (reader XLSXR_1) [off]
    attributes: Traffic sign for  char(101), service Category number(3,0), Pictogram Category number(4,0), Pictogram Category00 number(4,0), Related attributes char(31), U.N./Vienna char(18), Germany string, France string, UK string, Italy string, Spain string, Netherlands string, Belgium string, Switzerland string, Austria string, Ireland string, Poland string, Sweden string, Finland string, Norway string, Greece string, Czech Rep string, Slovakia string, Russia & Belarus string, U.S. string, South Korea string, Japan string, AB string
    -> AttributeManager_4
AttributeManager_4
    ATTR_TABLE:
      RENAME_SET_VALUE GDD code > signCategory
      RENAME_SET_VALUE GDD code00 > signSymbol
      RENAME_SET_VALUE Traffic sign for  > Description
      REMOVE service Category
      REMOVE Pictogram Category
      REMOVE Pictogram Category00
      REMOVE Related attributes
      REMOVE U.N./Vienna
      REMOVE Germany
      REMOVE France
      REMOVE UK
      REMOVE Italy
      REMOVE Spain
      REMOVE Netherlands
      REMOVE Belgium
      REMOVE Switzerland
      REMOVE Austria
      REMOVE Ireland
      REMOVE Poland
      REMOVE Sweden
      REMOVE Finland
      REMOVE Norway
      REMOVE Greece
      REMOVE Czech Rep
      REMOVE Slovakia
      REMOVE Russia & Belarus
      REMOVE U.S.
      REMOVE South Korea
      REMOVE Japan
      REMOVE AA
      REMOVE AB
      REMOVE AC
      REMOVE Request by NL
      REMOVE Request by AT
      REMOVE Request by DE
      REMOVE AD
      REMOVE AE
      REMOVE AF
      REMOVE AG
      REMOVE AH
      REMOVE AI
      REMOVE AJ
      REMOVE AK
      REMOVE AL
      REMOVE AM
      REMOVE AN
      REMOVE GDD code01
    -> TestFilter_2
TestFilter_2
    DEFAULT_VALUE = <UNFILTERED>
    TEST_LIST:
      "BOOL_OP,AND,COMPOSITE_TEST,""""""<Unused>"""""",TEST_CLAUSE,TEST signCategory ATTRIBUTE_HAS_A_VALUE ""
      TEST signSymbol ATTRIBUTE_HAS_A_VALUE """,HasValue
    HasValue -> DuplicateFilter
    HasValue -> AttributeManager_7
DuplicateFilter
    INPUT_ORDERED_CHOICE = No
    KEYATTR = signCategory
    UNIQUE -> AttributeManager_6
AttributeManager_6
    ATTR_TABLE:
      REMOVE Description
      SET_TO fme_feature_type = TrafficSignClassCode
      REMOVE signSymbol
      SET_TO gddCode = gdd@Value(signCategory)
    -> AttributeManager_5
AttributeManager_7
    ATTR_TABLE:
      SET_TO fme_feature_type = TrafficSignSymbolCode
      SET_TO gddCode = gdd@Value(signCategory)-@Value(signSymbol)
    -> AttributeManager_5
AttributeManager_5
    ATTR_TABLE:
      SET_TO xml =     <skos:Concept rdf:about="https://raw.githubusercontent.com/jetgeo/GIS2OWL/master/iso14823/@Value(fme_feature_type).rdf#@Value(gddCode)">
              <skos:inScheme rdf:resource="https://raw.githubusercontent.com/jetgeo/GIS2OWL/master/iso14823/@Value(fme_feature_type).rdf"/>
              <skos:prefLabel xml:lang="en">@Value(Description)</skos:prefLabel>
              <skos:definition xml:lang="en">@Value(Description)</skos:definition>
          </skos:Concept>
    -> ListBuilder_2
ListBuilder_2
    GROUPS_ORDERED = No
    GROUP_BY = fme_feature_type
    LIST_ATTRS_TO_INCLUDE = Description fme_feature_type gddCode signCategory signSymbol xml
    LIST_NAME = _list
    -> XMLTemplater_2 [ROOT]
XMLTemplater_2
    OUTPUT_XML_HEADER = Yes
    RESULT_ATTRIBUTE = _result
    ROOT_QUERY_EXPR:
      <rdf:RDF
        xmlns:skos="http://www.w3.org/2004/02/skos/core#"
        xmlns:rdf="http://www.w3.org/1999/02/22-rdf-syntax-ns#">
        {fme:get-list-attribute("_list{}.xml")}
      </rdf:RDF>
    VISIBLE_QUERY_VALIDATE = No
    -> StringReplacer_2
StringReplacer_2
    CASE = NO
    FIND_TEXT = &lt;
    NO_MATCH = _FME_NO_OP_
    REGEXP = NO
    REPLACE_TEXT = <
    SRC_ATTRS = _result
    -> StringReplacer_5
StringReplacer_5
    CASE = NO
    FIND_TEXT = &gt;
    NO_MATCH = _FME_NO_OP_
    REGEXP = NO
    REPLACE_TEXT = >
    SRC_ATTRS = _result
    -> AttributeManager_8
AttributeManager_8
    ATTR_TABLE = RENAME_SET_VALUE _result > text_line_data
    -> text_line (writer TEXTLINE_1)
text_line (writer TEXTLINE_1)
    attributes: text_line_data buffer
